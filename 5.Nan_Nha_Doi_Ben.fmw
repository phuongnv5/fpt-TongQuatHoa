FME workspace 5.Nan_Nha_Doi_Ben.fmw

Parameters:
- SourceDataset_GEODATABASE_FILE = C:\Generalize_25_50\50K_Process.gdb   # File Geodatabase
- SourceDataset_GEODATABASE_FILE_6 = C:\Generalize_25_50\50K_Process.gdb   # File Geodatabase
- DestDataset_GEODATABASE_FILE = C:\Generalize_25_50\50K_Final.gdb   # File Geodatabase
- DestDataset_GEODATABASE_FILE_2 = C:\Generalize_25_50\50K_Process.gdb   # File Geodatabase

Readers:
- GEODATABASE_FILE_1: GEODATABASE_FILE from $(SourceDataset_GEODATABASE_FILE)
- GEODATABASE_FILE_2: GEODATABASE_FILE from $(SourceDataset_GEODATABASE_FILE_6)

Writers:
- GEODATABASE_FILE_3: GEODATABASE_FILE to $(DestDataset_GEODATABASE_FILE)
- GEODATABASE_FILE_4: GEODATABASE_FILE to $(DestDataset_GEODATABASE_FILE_2)

DoanTimDuongBo_Goc (reader GEODATABASE_FILE_2)
    attributes: OBJECTID integer, maNhanDang char(16), ngayThuNhan date, ngayCapNhat date, maDoiTuong char(4), loaiDuongBo smallint, loaiChatLieuTraiMat smallint, loaiHienTrangSuDung smallint, loaiKetCau smallint, ten char(150), tenTuyen1 char(150), tenTuyen2 char(150), tenTuyen3 char(150), nguonDuLieu char(150), phanLoaiDuong smallint, Shape_Length double, maTrinhBay char(10), tenManh char(100), soPhienHieuManhBanDo char(20), doRongLongDuong double, doRongNenDuong double, DoanTimDuongBo_Rep_ID integer, DoanTimDuongBo_Rep_OVERRIDE blob, DoanTimDuongBo_Nen_ID integer, DoanTimDuongBo_Nen_OVERRIDE blob, hi smallint
    -> FeatureJoiner_2 [LEFT]
    -> NeighborFinder_2 [CANDIDATE]
NhaP (reader GEODATABASE_FILE_1)
    attributes: OBJECTID integer, maNhanDang char(16), ngayThuNhan date, ngayCapNhat date, maDoiTuong char(4), doiTuong smallint, ten char(200), chieuCao double, nguonDuLieu char(150), maTrinhBay char(10), tenManh char(100), soPhienHieuManhBanDo char(20), NhaP_Rep1_ID integer, NhaP_Rep1_OVERRIDE blob
    -> NeighborFinder_2 [BASE]
NeighborFinder_2
    CANDIDATES_FIRST = No
    CLOSE_LIST_ATTRS_TO_INCLUDE = OBJECTID
    CLOSE_LIST_ATTRS_TO_INCLUDE_MODE = Selected Attributes
    CLOSE_LIST_NAME = _nearest
    INSERT_VERTEX = No
    K = 1
    MAX = 50
    MEASURES_FROM_CANDIDATE = Yes
    MEASURE_TYPE = Continuous
    MODE = Bases and Candidates
    TREAT_POLYGON_AS = Lines
    MATCHED -> ExpressionEvaluator_3
    MATCHED -> FeatureJoiner_2 [RIGHT]
    UNMATCHED_BASE -> Sorter
FeatureJoiner_2
    ATTR_CONFLICT_RES = Use Left
    GEOMETRY_HANDLING = Use Left
    JOIN_KEYS = OBJECTID _nearest{0}.OBJECTID AUTO
    JOIN_MODE = Inner
    JOINED -> ExpressionEvaluator_4
ExpressionEvaluator_4
    ACTION = Create New Attribute
    EXPRESSION = @Value(OBJECTID)
    VAL_ATTR = LinkAttributed
    -> LeftRightSpatialCalculator_2 [BASE]
ExpressionEvaluator_3
    ACTION = Create New Attribute
    EXPRESSION = @Value(_nearest{0}.OBJECTID)
    VAL_ATTR = LinkAttributed
    -> LeftRightSpatialCalculator_2 [CANDIDATE]
LeftRightSpatialCalculator_2
    BASE_ID_ATTR = OBJECTID
    BASE_TYPE = Single Base
    GROUP_BY = LinkAttributed
    RELATIVE_POSITION_LIST_ATTR = _relative_position
    USE_BASE_CLOSEST_POINT = Yes
    USE_CANDIDATE_CENTER_OF_MASS = Yes
    -> LeftRightSpatialCalculator [CANDIDATE]
DoanTimDuongBo (reader GEODATABASE_FILE_2)
    attributes: OBJECTID integer, maNhanDang char(16), ngayThuNhan date, ngayCapNhat date, maDoiTuong char(4), loaiDuongBo smallint, loaiChatLieuTraiMat smallint, loaiHienTrangSuDung smallint, loaiKetCau smallint, ten char(150), tenTuyen1 char(150), tenTuyen2 char(150), tenTuyen3 char(150), nguonDuLieu char(150), phanLoaiDuong smallint, maTrinhBay char(10), tenManh char(100), soPhienHieuManhBanDo char(20), doRongLongDuong double, doRongNenDuong double, DoanTimDuongBo_Rep_ID integer, DoanTimDuongBo_Rep_OVERRIDE blob, DoanTimDuongBo_Nen_ID integer, DoanTimDuongBo_Nen_OVERRIDE blob, hi smallint, Shape_Length double, InLine_FID integer, SimLnFlag smallint, MaxSimpTol double, MinSimpTol double
    -> ExpressionEvaluator_2
    -> FeatureJoiner_3 [LEFT]
ExpressionEvaluator_2
    ACTION = Create New Attribute
    EXPRESSION = @Value(OBJECTID)
    VAL_ATTR = LinkAttributed
    -> LeftRightSpatialCalculator [BASE]
LeftRightSpatialCalculator
    BASE_ID_ATTR = OBJECTID
    BASE_TYPE = Single Base
    GROUP_BY = LinkAttributed
    RELATIVE_POSITION_LIST_ATTR = _relative_position_new
    USE_BASE_CLOSEST_POINT = Yes
    USE_CANDIDATE_CENTER_OF_MASS = Yes
    -> Tester
Tester
    BOOL_OP = OR
    TEST_CLAUSE = TEST @Value(_relative_position_new{0}.position) = @Value(_relative_position{0}.position)
    PASSED -> Sorter
    FAILED -> ExpressionEvaluator_5
ExpressionEvaluator_5
    ACTION = Create New Attribute
    EXPRESSION = @Value(OBJECTID)
    VAL_ATTR = DiemSaiID
    -> CoordinateExtractor_4
    -> FeatureJoiner_3 [RIGHT]
    -> SpatialFilter [Filter]
    -> NeighborFinder_3 [BASE]
FeatureJoiner_3
    ATTR_CONFLICT_RES = Use Left
    GEOMETRY_HANDLING = Use Left
    JOIN_KEYS = OBJECTID _relative_position_new{0}.base_id AUTO
    JOIN_MODE = Inner
    JOINED -> Intersector
CoordinateExtractor_4
    IND = 0
    MODE = Specify Coordinate
    X_ATTR = _x
    Y_ATTR = _y
    Z_ATTR = _z
    -> 2DEllipseReplacer
2DEllipseReplacer
    PRIMAXIS = 50
    ROT = 0
    SECAXIS = 50
    XVALATTR = @Value(_x)
    YVALATTR = @Value(_y)
    ELLIPSE -> GeometryCoercer
GeometryCoercer
    GQUERY:
      for $geom in //geometry
      where $geom/count(parent::geometry) = 0
      return number($geom/@fme_id)
    KIND = fme_line
    COERCED -> Intersector
Intersector
    ATTRS_ACCUM_MODE = Use Attributes From One Feature
    CLEANING_TOLERANCE = None
    DEAGGREGATE_INPUT = Yes
    DUPLICATE_Z_NODES = No
    GENERATE_LIST_DROP = NO
    GRP_BY = DiemSaiID
    MEASURE_TYPE = Continuous
    NODE_NUM_ATTR = _node_number
    OV_ATTR = _overlaps
    PERFORM_SELF_INTERSECTION = No
    SEG_ATTR = _segments
    SEPARATE_COLLINEAR_SEGMENTS = No
    INTERSECTED -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    GROUP_BY = LinkAttributed
    LINES_AS_SEGMENTS = No
    POLY_ACCUM_ATTRS_NAME = Use Attributes From One Feature
    SNAPTYPE_PARAM = None
    AREA -> SpatialFilter [Candidate]
SpatialFilter
    AGGREGATE_HANDLING = Yes
    BASE_TYPE = Multiple Filters
    CURVE_BOUNDARY_RULE_PARAM = Default Rule
    GROUP_BY = LinkAttributed
    PASS_CRITERIA = Pass Against One Filter
    PREDATTR = _predicate
    PREDICATES = WITHIN
    USE_BOUNDING_BOX = No
    FAILED -> CenterPointReplacer
CenterPointReplacer
    MODE = Inside Point
    POINT -> CoordinateExtractor_2
CoordinateExtractor_2
    IND = 0
    MODE = Specify Coordinate
    X_ATTR = _x
    Y_ATTR = _y
    Z_ATTR = _z
    -> NeighborFinder_3 [CANDIDATE]
NeighborFinder_3
    CANDIDATES_FIRST = No
    CLOSE_LIST_ATTRS_TO_INCLUDE = _x _y _z
    CLOSE_LIST_ATTRS_TO_INCLUDE_MODE = Selected Attributes
    CLOSE_LIST_NAME = _replaced
    GROUP_BY = LinkAttributed
    INSERT_VERTEX = No
    K = 1
    MAX = 50
    MEASURES_FROM_CANDIDATE = Yes
    MEASURE_TYPE = Continuous
    MODE = Bases and Candidates
    TREAT_POLYGON_AS = Lines
    MATCHED -> VertexCreator_4
VertexCreator_4
    MODE_NAME = Replace with Point
    XVAL = @Value(_replaced{0}._x)
    YVAL = @Value(_replaced{0}._y)
    -> Sorter
Sorter
    SORT_PARM = OBJECTID ALPHA ASCENDING
    SORTED -> NhaP (writer GEODATABASE_FILE_3)
    SORTED -> NhaP (writer GEODATABASE_FILE_4)
NhaP (writer GEODATABASE_FILE_3)
    attributes: OBJECTID integer, maNhanDang char(16), ngayThuNhan date, ngayCapNhat date, maDoiTuong char(4), doiTuong smallint, ten char(200), chieuCao double, nguonDuLieu char(150), maTrinhBay char(10), tenManh char(100), soPhienHieuManhBanDo char(20), NhaP_Rep1_ID integer, NhaP_Rep1_OVERRIDE blob
NhaP (writer GEODATABASE_FILE_4)
    attributes: OBJECTID integer, maNhanDang char(16), ngayThuNhan date, ngayCapNhat date, maDoiTuong char(4), doiTuong smallint, ten char(200), chieuCao double, nguonDuLieu char(150), maTrinhBay char(10), tenManh char(100), soPhienHieuManhBanDo char(20), NhaP_Rep1_ID integer, NhaP_Rep1_OVERRIDE blob
